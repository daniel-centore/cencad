;;************
;;Use this to load all of our lisp files ahead of time so we can call them later on from the mnu file
;;Make sure you dont include the .lsp extension when loading them
;;
;;Format: (load "filename" '("command1" "command2" "command3" "etc"))
;;                         ^ that is NOT a typo
;;
;;Written for Centek Engineering (http://www.centekeng.com/)
;;Author: Daniel Centore (dcentore@optonline.net)
;;*************

;Begin loading all required files

(setvar "cmdecho" 0)		    ;Disable other commands from printing
;(setvar "glswapmode" 0)	    ;fixes ati graphics issue


(setq PROMPTMENU 0)                 ;Disable the annoying prompt menu
(setq GRIDUNIT 120,120)             ;Sets the grid size to a reasonable one (autocad default)

;; 10.6-->. We go out so many places so we don't get funky decimals when dividing
(setq text-var 10.66666666666666)
(setq text-size (/ (getvar "dimscale") text-var))

;load linetypes
(command "-linetype" "load" "*" (findfile "acad.lin") ^C^C)

;load all helper files (seem to only need to load one method?)
(load "readcsv" '("loadblockinfo"))
(load "customcomm" '("revcloud"))
(load "dline" '("dline"))
(load "infogetter" '("getlinestart" "getlineend"))
(load "userinput" '("getreal-def"))
(load "stringfunctions" '("char-array"))
(load "customhvac" '("to-demo-hvac"))
(load "customelec" '("wiremoldprewired"))
(load "customteldata" '("wirebreakend"))
(load "autobreaktxt" '("autobreaktext"))
(load "annotation" '("quickarrow"))
(load "customplum" '("insertbreak"))

;userinput
(loaddefaults)

;command used for testing o/ commands
(defun c:cw ()
	(print "======================")
	(c:quickarrow)
	(print "======================")
	(princ)
)

;;Inserts a block
;;
;;blockpath	The file path to the blob (or "" to not insert any)
;;layername	The layer to insert onto
;;color		Color to set the layer to
;;linetype	The linetype to set the layer to
;;rotation	How much to rotate by (-1 for prompt)
;;position	0=Prompt, -1=Use former
;;xcommand	A command that should be excecuted afterwards. Separate with ';' for progn effect.
;;xscale	-1=Current Scale, Other=Use that as scale
(defun insertblock (blockpath layername color linetype rotation position xcommand xscale)	;;dont set any temp vars here - it needs them as public
	(begincommand)
	(if (= xcommand '()) (*error* "xcommand is nil"))
	(setq xcommand (split xcommand ";"))
	
	(if (/= (equal layername "") t) (command "._layer" "_M"    layername ""))
	(if (/= (equal color "")     t) (command "-layer"  "color" color     "" ""))
	(if (/= (equal linetype "")  t) (command "-layer"  "ltype" linetype  "" ""))

	(if (/= (equal blockpath "") t) (progn 	;if we dont have a block to insert, then dont!
	
		(setq scale (getvar "dimscale"))
		
		(if (/= (equal xscale "-1" ) t) (setq scale xscale))
		
		;(if (equal position "0") (setq ins_pt (getpoint "\nPick Insertion point.")))
		
		(command "-insert" blockpath "_non")
		(command "s" scale)
		(if (/= (equal position "0") t) 
			;;IF
			(command ins_pt)
			;;ELSE
			(progn
			(prompt "\nPick insertion point: ")
			(command pause)
			(setq ins_pt (getvar "lastpoint"))	
		))

		(setvar "cmdecho" 1)
		(if (equal rotation "-1") (progn (prompt "\nRotation angle for block <0>: ") (command pause)) (command rotation))
	))
	
	(foreach item xcommand (progn
		;;Note for xcommand: if the command is located within cencad, then it must be explicitly stated like DL below:
		(if (equal item "DL") (progn (setvar "tracewid" (* 0.03125 (getvar "dimscale"))) (c:dl))
		(if (/= (equal item "-1") t) (command item)
		))
	))
	
	;(while (/= (getvar "cmdactive") 0) (command pause))
	(setvar "cmdecho" 0)
	
	;;Lets set the attribute height now - must be AFTER the commands in case we decide to add attributes from there
	(if (/= (entlast) nil) (progn
		(set-attribute-height (entity-ename (entlast)) text-size)
	))

	(endcommand)
)

;;Sets up undo set
(defun begincommand ()	
	(command ".undo" "BE")		;Begin undo set
)

;;Ends command w/ (princ). Perhaps this will be needed later.
(defun endcommand ()
	(princ)
)

(setq disabled '())

;;Disables all snaps
(defun disablesnap ()
	(if (/= disabled t) (progn 
		;(print "disabled")
		(setq oldsnap (getvar "osmode"))
		(setq oldortho (getvar "orthomode"))
	
		(setvar "osmode" 0)		;turn off all snapping
		(setvar "orthomode" 0)		;turn off straight lines
	))
	
	(setq disabled t)
)

;;Re-enables snaps
(defun enablesnap ()
	;(print "enabled")
	(setvar "osmode" oldsnap)
	(setvar "orthomode" oldortho)
	
	(setq disabled '())
)

(defun c:enablesnap ()
	(enablesnap)
	(princ)
)

;;Clears the console by printing alotta lines
(defun c:clear ()
	(repeat 500 (prompt "\n"))
	
	(princ)
)

;;Converts a number to a string w/ 12-pt precision
(defun as-string (number / olddim result)
	(setq olddim (getvar "dimzin"))
	(setvar "dimzin" 15)
	
	(setq result (rtos number 2 12))
	
	(setvar "dimzin" olddim)
	
	result
)

;;Shortcut to zoom; extents
(defun c:extents ()
	(begincommand)
	(command "zoom" "e")
	(endcommand)
)

;;fixes prompt when it stops showing the :
;;
;;(4/16/11) Not sure if this is still a bug
(defun c:fixp ()
	(prompt "\n")
)

;;Reloads the lisp file
(defun c:rlsp ()
	(setq s::startup nil)
	(load (findfile "cencad.mnl"))
	(if s::startup (s::startup))
	(setq s::startup nil)
	(princ)
)

(defun c:entitydata ()
	;(begincommand)	;only 1 command dont bother
	
	(entget (car (entsel "Ah-choo: ")))
	
	;(endcommand)	;dont add this back - we lose the return val
)

;; just prints some info for user
(defun cleanprint (text)
	(prompt (strcat "\n" text "\n"))
	(princ)
)

;;Sets the style and such
(command "-style" "CEN-ATT" "romans.shx" (as-string text-size) "0.75" "0" "no" "no")
(c:clear)
(prompt "\nCENCAD is READY for you to use :-)")
(prompt "\nIf you find any bugs, please report them to Daniel Centore <dcentore@optonline.net>")

;;Prompts for drawing scale (remove for production versions)
;(drawingsetup)
